module service-function-acl {
  yang-version 1;

  namespace "urn:cisco:params:xml:ns:yang:sfc-acl";

  prefix sfc-acl;

  import ietf-access-control-list {
    prefix ietf-acl;
    revision-date 2016-02-18;
  }
  import ipfix-application-information {
    prefix ipfix-application-information;
    revision-date 2015-04-10;
  }

  organization "Cisco Systems, Inc.";
  contact "Reinaldo Penno <repenno@cisco.com>";

  revision 2015-10-01 {
    description "creating Service Function Chaining extensions to ietf-acl model";
  }

  augment "/ietf-acl:access-lists/ietf-acl:acl/ietf-acl:access-list-entries/ietf-acl:ace/ietf-acl:actions" {
    description "SFC simple filter actions";
    choice sfc-action {
    case acl-rendered-service-path {
      description "Determine the Service Function Path the packet the packet will
      traverse";
      leaf rendered-service-path {
        type string;
      }
     }
    }
  }
  augment "/ietf-acl:access-lists/ietf-acl:acl/ietf-acl:access-list-entries/ietf-acl:ace/ietf-acl:matches" {
	    description "Level 7 match criteria, based on IPFIX applicationIds";
	    leaf-list application-id {
	      description "Application Identifier";
	      type ipfix-application-information:application-id-ref;
	    }
	  }
  container access-lists-state {
    description
      "This container hold operational state for all access lists";
    config false;

    list access-list-state {
      description
        "This list holds operational data for all access lists
         in the domain";
      key "acl-type acl-name";
      leaf acl-name {
        type string;
        description
          "The name of the acl";
      }
      leaf acl-type {
        type ietf-acl:acl-type;
        description
            "Type of the acl";
      }

      list acl-service-function-classifier {
        key "name";
        leaf name {
          type string;
          description
            "The name of the classifier";
        }
        description
        "A list of all classifiers that use rules from this access list";
      }
    }
  }
}
